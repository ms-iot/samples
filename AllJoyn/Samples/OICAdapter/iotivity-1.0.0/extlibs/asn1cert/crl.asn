CRL DEFINITIONS ::= BEGIN

CertificateRevocationList  ::=  SEQUENCE  {
    tbsCertList          TBSCertList,
    signatureAlgorithm   AlgorithmIdentifier,
    signatureValue       BIT STRING  }

TBSCertList  ::=  SEQUENCE  {
    signature               AlgorithmIdentifier,
    issuer                  Name,
    thisUpdate              Time,
    revokedCertificates     SEQUENCE OF CertificateRevocationInfo
                           }

CertificateRevocationInfo ::= SEQUENCE  {
    userCertificate         CertificateSerialNumber,
    revocationDate          Time
          }

AlgorithmIdentifier ::= SEQUENCE {
    algorithm       	OBJECT IDENTIFIER,
    id-ecPublicKey 	OBJECT IDENTIFIER OPTIONAL,
    nul			NULL OPTIONAL
}

CertificateSerialNumber ::= INTEGER

Time ::= UTCTime

Name ::= RDNSequence

RDNSequence ::= SEQUENCE OF RelativeDistinguishedName

RelativeDistinguishedName ::= SET OF AttributeTypeAndValue

AttributeTypeAndValue ::= SEQUENCE {
     type     AttributeType,
     value    AttributeValue }

AttributeType ::= OBJECT IDENTIFIER

AttributeValue ::= UTF8String

END
